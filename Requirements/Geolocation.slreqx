# Geolocation

## Location: Must know where it is located (Functional)
Must be able to locate itself in a pre-loaded map of a 3D space.

### Location of Charging pad: should know the location of the nearest charger. (Functional)
The drone should always know the location of the nearest charging pad so that it can navigate to it when needed.

## 3D Map Storaage (Functional)
Must be able to store a 3D map of the location in memory.
