# Flight Computer

## Override: must be able to take manual control (Functional)
Users must be able to override automatic flight to take control

## Manual Control (Functional)
must include interface for user to take manual control (joystick)
