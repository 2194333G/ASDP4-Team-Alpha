# Platform

## Camera: HD Quality (Functional)
Must have a good quality camera (720p)
- Keywords: camera, good, like really good

### Additional Functions: extra camera abilities (Functional)
Have infra-red, thermal and/or night-vision capabilities.

## Weight: Less than 350g (Functional)
Minimise as much as possible, ideally <350g.

## Flight Time: At least 10mins (Functional)
Must be able to fly continuously for at least 10 minutes, ideally longer.

## Size: Must be portable (Functional)
must be easy to transport between locations.

## Cost: Must be kept low (Functional)
Cost must be kept as low as possible.

## Set-Up: Must be easy (Functional)
Drone cannot be complicated to set-up before use.

## Communication: Must have relevant communication tools. (Functional)
Must be able to communicate with ground control and other drones via bluetooth/wifi/other communication methods.

### Processing Load: must be minimised (Functional)
Processing done onboard the platform must be minimal to more efficiently use power, thereby increasing flight time.

## Obstacle sensor: for detecting new obstructions (Functional)
Must have a device for sensing obstructions that are not present on pre-loaded 3D map.
